module ietf-notification-sequencing {
  yang-version 1.1;
  namespace
    "urn:ietf:params:xml:ns:yang:ietf-notification-sequencing";
  prefix inotifseq;
  import ietf-inet-types {
    prefix inet;
    reference
      "RFC 6991: Common YANG Data Types";
  }
  import ietf-yang-types {
    prefix yang;
    reference
      "RFC 6991: Common YANG Data Types";
  }
  import ietf-notification {
    prefix inotif;
    reference
      "draft-ahuang-netconf-notif-yang: NETCONF Event Notification YANG";
  }
  import ietf-system-capabilities {
    prefix sysc;
    reference
      "RFC 9196: YANG Modules Describing Capabilities for
       Systems and Datastore Update Notifications";
  }
  import ietf-notification-capabilities {
    prefix notc;
    reference
      "RFC 9196: YANG Modules Describing Capabilities for
       Systems and Datastore Update Notifications";
  }
  import ietf-yang-structure-ext {
    prefix sx;
    reference
      "RFC 8791: YANG Data Structure Extensions";
  }

  organization "IETF NETCONF (Network Configuration) Working Group";
  contact
    "WG Web:   <http:/tools.ietf.org/wg/netconf/>
     WG List:  <mailto:netconf@ietf.org>

     Authors:  Thomas Graf
               <mailto:thomas.graf@swisscom.com>
               Jean Quilbeuf
               <mailto:jean.quilbeuf@huawei.com>
               Alex Huang Feng
               <mailto:alex.huang-feng@insa-lyon.fr>";

  description
    "Defines NETCONF Event Notification structure with the sysName and
    the sequenceNumber. 

    Copyright (c) 2024 IETF Trust and the persons identified as
    authors of the code.  All rights reserved.

    Redistribution and use in source and binary forms, with or without
    modification, is permitted pursuant to, and subject to the license
    terms contained in, the Revised BSD License set forth in Section
    4.c of the IETF Trust's Legal Provisions Relating to IETF Documents
    (https://trustee.ietf.org/license-info).

    This version of this YANG module is part of RFC XXXX; see the RFC
    itself for full legal notices.";

  revision 2023-06-30 {
    description
      "First revision";
    reference
      "RFC XXXX: YANG Notifications Sequencing";
  }

  feature sysname-sequence {
    description
      "This feature indicates that sysName and sequenceNumber are
      supported in notifications.";
  }

  typedef notification-support {
    type bits {
      bit config-changes {
        description
          "The publisher is capable of sending
          notifications for 'config true' nodes for the
          relevant scope and subscription type.";
      }
      bit state-changes {
        description
          "The publisher is capable of sending
          notifications for 'config false' nodes for the
          relevant scope and subscription type.";
      }
    }
    description
      "Redefition of the type 'notification-support' from 
      'ietf-notification-capabilities' module to be reusable in
      other YANG modules.

      Type for defining whether 'on-change' or
      'periodic' notifications are supported for all data nodes,
      'config false' data nodes, 'config true' data nodes, or
      no data nodes.

      The bits config-changes or state-changes have no effect
      when they are set for a datastore or for a set of nodes
      that does not contain nodes with the indicated config
      value.  In those cases, the effect is the same as if no
      support was declared.  One example of this is indicating
      support for state-changes for a candidate datastore that
      has no effect.";
    reference
      "RFC XXXX: YANG Notifications Sequencing
      RFC 9196: YANG Modules Describing Capabilities for
      Systems and Datastore Update Notifications";
  }

  sx:augment-structure "/inotif:notification" {
    leaf sysName {
      type inet:host;
      mandatory true;
      description
        "Fully-qualified domain name of the node according to
        [RFC1213]. This value is usually configured on the node
        by the administrator to uniquely identify the node in
        the network.";
    }
    leaf sequenceNumber {
      type yang:counter32;
      mandatory true;
      description
        "Generates a unique sequence number for each published message
        by the publisher process. The number counts up at every
        published notification message as described in [RFC9187].";
    }
  }

  augment "/sysc:system-capabilities/notc:subscription-capabilities" {
    description
      "Add system level capabilities";
    leaf sysname-sequence-supported {
      if-feature "sysname-sequence";
      type notification-support;
      description
        "Specifies whether the publisher supports exporting a
        sysName and a sequenceNumber in notifications.";
      reference
        "RFC XXXX: YANG Notifications Sequencing";
    }
  }
}
